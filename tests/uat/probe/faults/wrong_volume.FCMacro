# Fault: the box is 31 mm high, not 30 (volume 6200, not 6000).
import fault_scene
import Part

doc = fault_scene.open_clean_scene()
doc.getObject("Box").Shape = Part.makeBox(10, 20, 31)
fault_scene.mark_planted()
